FME workspace test-network.fmw
Title: test-network
Description: DESCRIPTION
Regression tests expected network connectivity from an FME environment

Parameters:
- FileSharePath =   # Path to FME File Share (\\server\AGOL_Publishing)
- EventClosure_CSV = $(FileSharePath)\Data\Other\eventclosure.csv   # Event Closure Server Address

Readers:
- CSV2_1: CSV2 from $(EventClosure_CSV)

Creator:_TestAgol
    GEOMTYPE = Geometry Object
    NUM = 1
    CREATED -> HTTPCaller:_Agol
HTTPCaller:_Agol
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://nyc.maps.arcgis.com/home/index.html
    TRANSFER_TIMEOUT_LENGTH = 90
    USE_COOKIES = No
    VERIFY_SSL_CERTIFICATES = Yes
    -> Tester:_HttpCallerAgol
Tester:_HttpCallerAgol
    BOOL_OP = COMPOSITE
    COMPOSITE_TEST = 1 AND 2
    TEST_CLAUSE:
      TEST _response_body ATTRIBUTE_HAS_A_VALUE ""
      TEST @Value(_http_status_code) = 200
    TEST_MODE = TEST
    PASSED -> Logger:_HttpCallerAgol
    FAILED -> Terminator:_HttpCallerAgol
Logger:_HttpCallerAgol
    LOG_FEATURE = NONE
    MAXFEATS = 1
    MESSAGE = gisadmin can reach https://nyc.maps.arcgis.com/home/index.html
    SEVERITY = INFO
Terminator:_HttpCallerAgol
    MESSAGE:
      $(WORKSPACE_NAME) has failed calling https://nyc.maps.arcgis.com/home/index.html
      http status code: @Value(_http_status_code)
      response body: @Value(_response_body)
Creator:_TestGeoservice
    GEOMTYPE = Geometry Object
    NUM = 1
    CREATED -> HTTPCaller:_Geoservice
HTTPCaller:_Geoservice
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://geoservice.planning.nyc.gov/
    TRANSFER_TIMEOUT_LENGTH = 90
    USE_COOKIES = No
    VERIFY_SSL_CERTIFICATES = Yes
    -> Tester:_HttpCallerGeoservice
Tester:_HttpCallerGeoservice
    BOOL_OP = COMPOSITE
    COMPOSITE_TEST = 1 AND 2
    TEST_CLAUSE:
      TEST _response_body ATTRIBUTE_HAS_A_VALUE ""
      TEST @Value(_http_status_code) = 200
    TEST_MODE = TEST
    PASSED -> Logger:_HttpCallerGeoservice
    FAILED -> Terminator:_HttpCallerGeoservice
Logger:_HttpCallerGeoservice
    LOG_FEATURE = NONE
    MAXFEATS = 1
    MESSAGE = gisadmin can reach https://geoservice.planning.nyc.gov/
    SEVERITY = INFO
Terminator:_HttpCallerGeoservice
    MESSAGE:
      $(WORKSPACE_NAME) has failed calling https://geoservice.planning.nyc.gov/
      http status code: @Value(_http_status_code)
      response body: @Value(_response_body)
CSV (reader CSV2_1)
    attributes: server varchar(15)
    -> FeatureReader:_EventClosureGeoserver [INITIATOR]
FeatureReader:_EventClosureGeoserver
    ATTR_ACCUM_MODE = Only Use Result
    COMBINE_GEOM = Use Result
    COORDSYS = EPSG:2263
    DATASET = http://@Value(server):8080/geoserver/wfs?request=getcapabilities&version=1.1.0
    FORMAT = WFS
    INTERACT = NONE
    MAX_FEATURES = 1
    OUTPUT_FEATURES_DISPLAY = Schema and Data Features
    WFS_CONNECTION_TIMEOUT = 90
    WFS_DISABLE_AUTOMATIC_READER_TYPE_SELECTION = NO
    WFS_DISABLE_XML_NAMESPACE_PROCESSING = NO
    WFS_ENFORCE_PATH_CONTINUITY_BY = SNAPPING_END_POINTS
    WFS_FLATTEN_XML_FRAGMENTS = NO
    WFS_IGNORE_APPLICATON_SCHEMA = no
    WFS_IGNORE_GETFEATURE_ERROR = No
    WFS_LOCAL_CACHE_EXPIRY = 60
    WFS_MAP_COMPLEX_PROPERTIES_AS = Nested Attributes
    WFS_MAP_COVERAGES_AS_FEATURE_TYPES = NO
    WFS_MAP_EMBEDDED_OBJECTS_AS = ATTRIBUTES
    WFS_MAP_GEOMETRY_COLUMNS = YES
    WFS_MAP_PREDEFINED_GML_PROPERTIES = NO
    WFS_MAX_RESULT_FEATURES = 1
    WFS_PREFERRED_VERSION = 1.1.0
    WFS_PREFER_DATASET_URL = No
    WFS_PREFER_POST = No
    WFS_SELECTED_WFS_LAYERS = CECM_vw_StreetClosureL32_Polygon
    WFS_TRANSFER_TIMEOUT = 90
    WFS_USE_OLD_READER = NO
    WFS_USE_SEARCH_ENVELOPE = NO
    WFS_XML_FRAGMENTS_AS_DOCUMENTS = YES
    <OTHER> -> Logger:_EventClosureGeoserver
    <REJECTED> -> Terminator:_EventClosureGeoserver
Logger:_EventClosureGeoserver
    LOG_FEATURE = LOG_ONLY
    MAXCOORDS = 20
    MAXFEATS = 20
    MESSAGE = gisadmin can reach the event closure geoserver
    SEVERITY = INFO
Terminator:_EventClosureGeoserver
    MESSAGE = $(WORKSPACE_NAME) has failed calling http://@Value(server):8080/geoserver/wfs?request=getcapabilities&version=1.1.0
Creator:_TestHttp
    GEOMTYPE = Geometry Object
    NUM = 1
    CREATED -> HTTPCaller:_ginger
HTTPCaller:_ginger
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://ginger.nyc.gov/
    TRANSFER_TIMEOUT_LENGTH = 90
    USE_COOKIES = No
    VERIFY_SSL_CERTIFICATES = Yes
    -> Tester:_HttpCallerGinger
Tester:_HttpCallerGinger
    BOOL_OP = AND
    TEST_CLAUSE:
      TEST _response_body ATTRIBUTE_HAS_A_VALUE ""
      TEST @Value(_http_status_code) = 200
    TEST_MODE = TEST
    PASSED -> Logger:_HttpCallerGinger
    FAILED -> Terminator:_HttpCallerGinger
Logger:_HttpCallerGinger
    LOG_FEATURE = NONE
    MAXFEATS = 1
    MESSAGE = gisadmin can reach ginger.nyc.gov
    SEVERITY = INFO
Terminator:_HttpCallerGinger
    MESSAGE:
      $(WORKSPACE_NAME) Failed making an http call https://ginger.nyc.gov/
      http status code: @Value(_http_status_code)
      response body: @Value(_response_body)
Creator:_TestSFTP
    GEOMTYPE = Geometry Object
    NUM = 1
    CREATED -> FeatureReader:_GingerConfig [INITIATOR]
FeatureReader:_GingerConfig
    ATTRIBUTES = CSV,"user,credentials"
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(FileSharePath)\Data\Other\ginger.csv
    FEATURETYPES = CSV
    FORMAT = CSV2
    INTERACT = NONE
    OUTPUT_FEATURES_DISPLAY = Schema and Data Features
    CSV -> FTPCaller:_GingerSftp
FTPCaller:_GingerSftp
    AUTH_TYPE = AUTH_PASSWORD
    CONNECTION_MODE = PASSIVE
    ERROR_ATTR = _error
    FTP_PASSWORD = @Value(credentials)
    FTP_USERNAME = @Value(user)
    MODE = Binary
    PROXY_TYPE = FME
    REMOTE_URL = sftp://ginger.nyc.gov:22/GIS/whywasthe6scared.txt
    TARGET_ATTR = _file_contents
    TARGET_ATTR_ENCODING = utf-8
    TRANSFER_TYPE = Download to an Attribute
    VERIFY_SSL_CERTIFICATES = Yes
    -> Tester:_GingerSftpReadsFile
Tester:_GingerSftpReadsFile
    BOOL_OP = OR
    TEST_CLAUSE = TEST @Value(_file_contents) = because789
    TEST_MODE = TEST
    PASSED -> Logger:_GingerSftp
    FAILED -> Terminator:_GingerSftpReadsFile
Logger:_GingerSftp
    LOG_FEATURE = NONE
    MAXFEATS = 1
    MESSAGE = gisadmin can connect to ginger.nyc.gov over sftps
    SEVERITY = INFO
Terminator:_GingerSftpReadsFile
    MESSAGE:
      $(WORKSPACE_NAME) Failed testing an SFTP connection to ginger
      could not fetch file contents from
      sftp://ginger.nyc.gov:22/GIS/whywasthe6scared.txt

Bookmark: Implicit FTPS: Success on expected failure is too confusing we will disable this for now
Creator:_TestFTPS [off]
    GEOMTYPE = Geometry Object
    NUM = 1
    CREATED -> FeatureReader:_GingerFTPS [INITIATOR]
FeatureReader:_GingerFTPS [off]
    ATTRIBUTES = CSV,"user,credentials"
    ATTR_ACCUM_MODE = Only Use Result
    COMBINE_GEOM = Use Result
    CSV2_CASE_SENSITIVE_FIELD_NAMES = Yes
    CSV2_CHUNK_SIZE = 100000
    CSV2_DATA_START_LINE = 2
    CSV2_DATE_INPUT_FORMAT = ISO
    CSV2_DELIMITER = auto
    CSV2_ENCODING = windows-1252
    CSV2_ENFORCE_STRICT_SCHEMA = No
    CSV2_FEATURE_TYPE_NAME = FORMAT_NAME
    CSV2_FIELD_NAMES_LINE = 1
    CSV2_FIELD_QUALIFIER_CHARACTER = "
    CSV2_FIELD_QUALIFIER_ESCAPE_CHARACTER = "
    CSV2_PRESERVE_SOURCE_ENCODING = No
    CSV2_QUERY_FEATURE_TYPES_FOR_MERGE_FILTERS = Yes
    CSV2_READ_EMPTY_VALUES_AS = Null
    CSV2_READ_SKIPPED_LINES = No
    CSV2_REPLACE_ATTR_NAME_INVALID_CHARS = Yes
    CSV2_SCAN_ADDITIONAL_FIELDS = No
    CSV2_SCAN_MAX_ROWS = 10000
    CSV2_SCAN_TYPES = Yes
    CSV2_SKIP_DUPLICATE_DELIMITERS = No
    CSV2_STRING_TYPE_ATTRIBUTE_HANDLING = EXPLICIT_WIDTH
    CSV2_SUPPORTED_READER_ARCHIVE_EXTENSIONS = csv.gz,txt.gz
    CSV2_TRIM_FEATURE_TYPE_NAME = Yes
    CSV2_TRIM_FIELD_NAME_QUALIFIERS = Yes
    CSV2_TRIM_FIELD_NAME_WHITESPACE = Yes
    CSV2_TRIM_FIELD_VALUE_QUALIFIERS = Yes
    CSV2_TYPE_ATTRIBUTE_HANDLING = STANDARD_TYPES
    CSV2_USE_CUSTOM_SCHEMA = NO
    DATASET = $(FileSharePath)\Data\Other\ginger.csv
    FEATURETYPES = CSV
    FORMAT = CSV2
    INTERACT = NONE
    OUTPUT_FEATURES_DISPLAY = Schema and Data Features
    CSV -> FTPCaller:_GingerFtps
Note: SSL Connect Error / FTPS connections to ginger must _require_ implicit FTP over TLS and SOCKS5 proxy
FTPCaller:_GingerFtps [off]
    AUTH_TYPE = AUTH_PASSWORD
    CONNECTION_MODE = PASSIVE
    ERROR_ATTR = _error
    FTP_PASSWORD = @Value(credentials)
    FTP_USERNAME = @Value(user)
    MODE = Binary
    PROXY_TYPE = FME
    REMOTE_URL = ftps://ginger.nyc.gov:990/GIS/whywasthe6scared.txt
    TARGET_ATTR = _file_contents
    TARGET_ATTR_ENCODING = utf-8
    TRANSFER_TYPE = Download to an Attribute
    VERIFY_SSL_CERTIFICATES = No
    -> Terminator:_GingerFTPSReadsFile
    <REJECTED> -> Logger:_GingerFTPS
Note: Success/Fail port flipperoo? Get red in the logs but call it a success? / Too clever pal you are not ready for this
Logger:_GingerFTPS [off]
    LOG_FEATURE = NONE
    MAXFEATS = 1
    MESSAGE = As expected gisadmin can not connect to ginger.nyc.gov on port 990 using implicit FTP over TLS
    SEVERITY = INFO
Terminator:_GingerFTPSReadsFile [off]
    MESSAGE:
      $(WORKSPACE_NAME) succeeded using an FTPS connection to ginger
      ALERT THE MEDIA
      we can now fetch file contents from ftps://ginger.nyc.gov:990/GIS/whywasthe6scared.txt

FME workspace test-database.fmw
Title: test-database
Description: DESCRIPTION
Regression tests expected database connectivity from an FME environment

Creator:_PscsclAzure
    GEOMTYPE = Geometry Object
    NUM = 1
    CREATED -> SQLExecutor:_PscsclAzure [INITIATOR]
SQLExecutor:_PscsclAzure
    COMBINE_ATTRS = Result Attributes Only
    COMBINE_GEOM = Initiator Geometry Only
    DATASET = sde_pscscl
    EXPOSED_ATTRIBUTE_LIST = dummy
    FORMAT = POSTGRES
    OUTPUT_FEATURES_DISPLAY = Data Features
    POSTGRES_CREATE_FEATURE_TABLES_FROM_DATA = Yes
    POSTGRES_NAMED_CONNECTION = sde_pscscl
    POSTGRES_QUERY_FEATURE_TYPES_FOR_MERGE_FILTERS = Yes
    POSTGRES_READ_TIME_WITH_TIMEZONE = Yes
    SQL_STATEMENT = select 1 as dummy
    INITIATOR -> Logger:_PscsclAzure
    <REJECTED> -> Terminator:_PscsclAzure
Logger:_PscsclAzure
    LOG_FEATURE = LOG_ONLY
    MAXCOORDS = 20
    MAXFEATS = 20
    MESSAGE = FME can connect to pscscl on azure
    SEVERITY = INFO
Terminator:_PscsclAzure
    MESSAGE:
      FME cannot connect to pscscl on azure.
      $(WORKSPACE_NAME) HAS FAILED WITH ERROR @Value(_reader_error)
Creator:_GisOnPremiseDatabase
    GEOMTYPE = Geometry Object
    NUM = 1
    CREATED -> SQLExecutor:_GisOnPremiseDatabase [INITIATOR]
SQLExecutor:_GisOnPremiseDatabase
    COMBINE_ATTRS = Result Attributes Only
    COMBINE_GEOM = Initiator Geometry Only
    DATASET = BLDG_READONLY_test
    EXPOSED_ATTRIBUTE_LIST = DUMMY
    FORMAT = ORACLE_NONSPATIAL
    ORACLE_NONSPATIAL_CREATE_FEATURE_TABLES_FROM_DATA = Yes
    ORACLE_NONSPATIAL_NAMED_CONNECTION = BLDG_READONLY_test
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    OUTPUT_FEATURES_DISPLAY = Schema and Data Features
    SQL_STATEMENT = select dummy from dual
    INITIATOR -> Logger:_GisOnPremiseDatabase
    <REJECTED> -> Terminator:_GisOnPremiseDatabase
Logger:_GisOnPremiseDatabase
    LOG_FEATURE = LOG_ONLY
    MAXCOORDS = 20
    MAXFEATS = 20
    MESSAGE = FME can connect to the GIS on premise database
    SEVERITY = INFO
Terminator:_GisOnPremiseDatabase
    MESSAGE:
      FME cannot connect to the GIS on premise database
      $(WORKSPACE_NAME) HAS FAILED WITH ERROR @Value(_reader_error)
Creator:_CsclOnPremiseDatabase
    GEOMTYPE = Geometry Object
    NUM = 1
    CREATED -> SQLExecutor:_CsclOnPremiseDatabase [INITIATOR]
SQLExecutor:_CsclOnPremiseDatabase
    COMBINE_ATTRS = Result Attributes Only
    COMBINE_GEOM = Initiator Geometry Only
    DATASET = CSCL_READ_ONLY_test
    EXPOSED_ATTRIBUTE_LIST = DUMMY
    FORMAT = ORACLE_NONSPATIAL
    ORACLE_NONSPATIAL_CREATE_FEATURE_TABLES_FROM_DATA = Yes
    ORACLE_NONSPATIAL_NAMED_CONNECTION = CSCL_READ_ONLY_test
    ORACLE_NONSPATIAL_PERSISTENT_CONNECTION = YES
    ORACLE_NONSPATIAL_QUERY_FEATURE_TYPES_FOR_MERGE_FILTERS = Yes
    ORACLE_NONSPATIAL_REMOVE_SCHEMA_QUALIFIER = NO
    ORACLE_NONSPATIAL_SERVER_TYPE = ORACLE8i
    ORACLE_NONSPATIAL_SHOW_SYSTEM_TABLES = NO
    ORACLE_NONSPATIAL_USE_UNIFIED_DATE_ATTRS = YES
    OUTPUT_FEATURES_DISPLAY = Schema and Data Features
    SQL_STATEMENT = select dummy from dual
    INITIATOR -> Logger:_CsclOnPremiseDatabase
    <REJECTED> -> Terminator:_CsclOnPremiseDatabase
Logger:_CsclOnPremiseDatabase
    LOG_FEATURE = LOG_ONLY
    MAXCOORDS = 20
    MAXFEATS = 20
    MESSAGE = FME can connect to the CSCL on premise database
    SEVERITY = INFO
Terminator:_CsclOnPremiseDatabase
    MESSAGE:
      FME cannot connect to the CSCL on premise database
      $(WORKSPACE_NAME) HAS FAILED WITH ERROR @Value(_reader_error)
